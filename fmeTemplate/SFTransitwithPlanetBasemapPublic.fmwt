FME workspace SFTransitwithPlanetBasemapPublic.fmwt
Title: SFTransitwithPlanetBasemapPublic
Description: The workspace reads the latest 
        Planet 
    imagery available through Planet Explorer program (two weeks back from the current date) and adds it as a base background map for San Francisco transit system read directly from 
        SFMTA 
    web site. 
The results of the working demo of this workspace are here:
        http://demos.fmeserver.com/satellite-imagery-planet/ 
With a paid Planet account, it is possible to get the most recent imagery. In order to get access to Planet data, you need to 
        sign up 
    for an API key, which should be set in two FeatureReaders reading Planet data.
The workspace reads the images, mosaics them together, and then overlays on top of the older basemap image to fill the empty space in cases when the new coverage is less than 100%.
If the image is available, it triggers reading of the transit data, which get styled and rasterized on top of the image with MapnikRasterizer. The final raster is turned into a web tile cache (a set of PNG files structured in a certain order for easy access via web mapping platforms such as Google Maps or Leaflet).
The products can be used locally or uploaded directly to web (the demo shows how to use Amazon S3 storage).
The workspace won't run "as is" - it requires Planet API key and valid S3 parameters. For local use, enable parts related to this use scenario (writers and transformers), disable S3 transformers, and make sure the links are connected correctly.
History: ,20170609,Dmitri Bagh,Created,,

Parameters:
- DestDataset_GEOTIFF = $(FME_MF_DIR)SFTransitwithPlanetBasemapPublic/SF\basemap   # Destination GeoTIFF Folder
- CLOUDCOVERAGE = 10   # Cloud coverage <= (%)
- BLACKFILL = 90   # Black fill <= (%)
- DestDataset_GEOTIFF_3 = $(FME_MF_DIR)SFTransitwithPlanetBasemapPublic/Output   # Destination GeoTIFF Folder
- DestDataset_PNGRASTER = $(FME_MF_DIR)SFTransitwithPlanetBasemapPublic/SF\tiles   # Destination PNG (Portable Network Graphics) Folder

Writers:
- GEOTIFF_1: GEOTIFF to $(DestDataset_GEOTIFF)
- GEOTIFF_2: GEOTIFF to $(DestDataset_GEOTIFF_3)
- PNGRASTER_1: PNGRASTER to $(DestDataset_PNGRASTER)

Bookmark: Making the new background map
Note: Create a rectangle covering / San Francisco transit system
Creator_3
    NUM = 1
    COORDS = -122.55 37.69 -122.35 37.85
    GEOMTYPE = 2D Coordinate List
    COORDSYS = LL84
    CREATED -> AttributeCreator
Note: Create a date attribute two weeks back from now / (for a free Planet Explorer program, / if you have a paid account, get the latest) / Create the second date attribute as date+1 day
AttributeCreator
    ATTR_TABLE:
      SET_TO _startdate = @DateTimeFormat(@DateTimeAdd(@DateTimeNow(),-P16D),%Y%m%d)
      SET_TO _enddate = @DateTimeFormat(@DateTimeAdd(@DateTimeNow(),-P15D),%Y%m%d)
    -> JSONTemplater [ROOT]
    -> Reprojector
Note: San Francisco data comes in UTM projection zone 10, / so we reproject the initial rectangle to this projection
Reprojector
    SOURCE = Read from feature
    RASTER_CELL_SIZE = Preserve Cells
    DEST = UTM83-10
    INTERPOLATION_TYPE_NAME = Nearest Neighbor
    REPROJECTED -> BoundingBoxReplacer_2
Note: to make a rectangle, / replace the reprojected feature / with its bounding box
BoundingBoxReplacer_2
    BOXTYPE = Bounding Box
    BOX -> Clipper [CLIPPER]
Note: Create cloud and data coverage filter
JSONTemplater
    RESULT_ATTRIBUTE = _json_filter
    ROOT_QUERY_EXPR = {"type" : "RangeFilter", "field_name" : "cloud_cover", "config" : { "lte" : @Evaluate($(CLOUDCOVERAGE)/100) }}
    VISIBLE_QUERY_VALIDATE = Yes
    -> FeatureReader [INITIATOR]
Note: Try to read RapidEye data for the selected date
FeatureReader
    PLANETDATA_CUSTOM_FILTER = @Value(_json_filter)
    PLANETDATA_CLIP_TO_ENVELOPE = NO
    PLANETDATA_ITEM_TYPE = REOrthoTile
    PLANETDATA_END_DATE = @Value(_enddate)
    PLANETDATA_START_DATE = @Value(_startdate)
    OUTPUT_FEATURES_DISPLAY = Schema and Data Features
    PLANETDATA_INCLUDE_JSON = Yes
    FEATURETYPES = visual
    ATTR_ACCUM_MODE = Only Use Result
    ATTRS_TO_EXPOSE = fme_basename
    COMBINE_GEOM = Use Result
    PLANETDATA_USE_SEARCH_ENVELOPE = NO
    INTERACT = Envelope Intersects
    FORMAT = PLANETDATA
    <OTHER> -> RasterMosaicker
    INITIATOR -> Tester
Note: If there is no RapidEye images on that date...
Tester
    BOOL_OP = OR
    TEST_CLAUSE = TEST @Value(_matched_records) = 0
    TEST_DESCRIPTION = ""
    TEST_MODE = Automatic
    PASSED -> FeatureReader_2 [INITIATOR]
Note: ...try reading PlanetScope images
FeatureReader_2
    PLANETDATA_CUSTOM_FILTER = @Value(_json_filter)
    PLANETDATA_CLIP_TO_ENVELOPE = NO
    PLANETDATA_ITEM_TYPE = PSScene3Band
    PLANETDATA_END_DATE = @Value(_enddate)
    PLANETDATA_START_DATE = @Value(_startdate)
    OUTPUT_FEATURES_DISPLAY = Schema and Data Features
    PLANETDATA_INCLUDE_JSON = Yes
    FEATURETYPES = visual
    ATTR_ACCUM_MODE = Only Use Result
    ATTRS_TO_EXPOSE = fme_basename
    COMBINE_GEOM = Use Result
    PLANETDATA_USE_SEARCH_ENVELOPE = NO
    INTERACT = Envelope Intersects
    FORMAT = PLANETDATA
    <OTHER> -> RasterMosaicker
Note: Mosaic multiple rasters
RasterMosaicker
    INTERPOLATION_TYPE_NAME = Bicubic
    MERGE_PALETTES_NAME = Yes
    OVERLAPPING_VALUES = composite_using_alpha
    ACCUM_ATTRS_NAME = Use Attributes From One Feature
    SNAPPING_TYPE_NAME = Resample
    -> Clipper [CLIPPEE]
Note: Clip the mosaic to the bounding box
Clipper
    CONNECT_Z_MODE = First Wins
    ATTR_CONFLICT_RES = Use Clippee
    DEFAULT_VAL = 0
    CLIPPED_ATTR = _clipped
    LINES_AS_SEGMENTS = No
    CREATE_AGGREGATES = Yes
    MEASURE_TYPE = Continuous
    MISSING_VAL_MODE = Compute
    BOUNDARY_CASES = Treat as Inside
    CLIP_TYPE = Multiple Clippers
    ATTR_ACCUM_MODE = Merge Clipper
    PRESERVE_CLIPPEE_EXTENTS = No
    VAL_SOURCE = Clippee Only
    INSIDE -> AttributeCreator_3
    INSIDE -> FeatureReader_3 [INITIATOR]
    INSIDE -> S3Downloader
Note: Read local copy of the previous mosaic...
FeatureReader_3 [off]
    GEOTIFF_IGNORE_RASTER_TYPE_KEY = No
    GEOTIFF_READ_OFFSETS_IN_CS_UNITS = No
    GEOTIFF_PREFER_FILE_CS_UNITS = Yes
    OUTPUT_FEATURES_DISPLAY = Schema and Data Features
    GEOTIFF_READER_META_ATTRIBUTES = fme_dataset fme_basename
    GEOTIFF_FEATURE_TYPE_NAME = FORMAT_NAME
    ATTR_ACCUM_MODE = Only Use Result
    COMBINE_GEOM = Use Result
    DATASET = $(FME_MF_DIR)1/basemap/basemap.tif
    INTERACT = <No Spatial Filter>
    FORMAT = GEOTIFF
    ATTRIBUTES = GEOTIFF,
    GEOTIFF_APPLY_GCPS = No
    GEOTIFF_USE_SEARCH_ENVELOPE = NO
    GEOTIFF -> AttributeCreator_2
Note: ...Or read it from your web storage / into an attribute
S3Downloader
    S3_ACCELERATION = No
    S3_BUCKET_NAME = your bucket
    S3_TARGET_ATTRIBUTE = _s3_object_contents
    TARGET_ATTR_ENCODING = auto-detect
    S3_OBJECT_KEY = Planet/basemap/basemap.tif
    S3_AWS_REGION = US West, Oregon (us-west-2)
    S3_FILE_OR_ATTRIBUTE = Attribute
    -> RasterReplacer
    <REJECTED> -> S3Downloader__Rejected_
Note: restore raster geometry / from the attribute
RasterReplacer
    REMOVE_ATTRIBUTE = Yes
    BLOB_ATTR = _s3_object_contents
    FORMAT = GEOTIFF
    -> AttributeCreator_2
S3Downloader__Rejected_: Logger
    MAXFEATS = 20
    MESSAGE = No previous image
    MAXCOORDS = 20
Note: We need to overwrite the previous basemap map. / In order to do so, we need to save an intermediate resiult here / otherwise the output may get corrupted. / Keeping a full copy of the map for future updates is necessary / for the cases when the update does not cover 100% of the area - / the empty pixels will be taken from the old image
RasterCheckpointer
    -> RasterMosaicker_2
Note: Mosaic the old and the new / (really needed only when / the new image has less than / 100% coverage)
RasterMosaicker_2
    INTERPOLATION_TYPE_NAME = Bicubic
    MERGE_PALETTES_NAME = Yes
    OVERLAPPING_VALUES = composite_using_alpha
    ACCUM_ATTRS_NAME = Use Attributes From One Feature
    SNAPPING_TYPE_NAME = Resample
    -> basemap (writer GEOTIFF_1)
    -> MapnikRasterizer [Background]
    -> RasterExtractor_2
Note: Save a local copy of the Planet basemap...
basemap (writer GEOTIFF_1) [off]
Note: Upload the date attribute as a json file to S3 storage / for using in an HTML description of the results
S3Uploader_4
    S3_ACCELERATION = No
    S3_BUCKET_NAME = your bucket
    S3_CANNED_ACL = Public Read
    S3_DATA = @Value(latest_update)
    S3_URI_ATTRIBUTE = _s3_object_uri
    S3_UPLOAD_ENCRYPTION = None
    S3_OBJECT_KEY = Planet/basemap/latest_update.json
    S3_AWS_REGION = US West, Oregon (us-west-2)
    S3_FILE_OR_DATA = Attribute or Expression
    -> S3Uploader_4_Output
S3Uploader_4_Output: Logger
    MAXFEATS = 20
    MESSAGE = Feature is:
    MAXCOORDS = 20

Bookmark: Sort the rasters so that the old goes underneath the new raster
Note: Create sort attribute
AttributeCreator_2
    ATTR_TABLE = SET_TO _sort = 0
    -> Sorter
Note: Create sort attribute / and the date attribute / when the image was taken
AttributeCreator_3
    ATTR_TABLE:
      SET_TO _sort = 1
      SET_TO latest_update = jsonDate = '{"date" : "@DateTimeFormat(@Left(@Value(fme_basename),8), %B %e %Y)"}';
    -> Sorter
    -> S3Uploader_4
Sorter
    SORT_PARM = _sort NUMERIC ASCENDING
    SORTED -> RasterCheckpointer

Bookmark: ... or upload it to S3
RasterExtractor_2
    RASTER_BLOB_ATTR = _rasterBlob
    RASTER_FORMAT = GeoTIFF (Geo-referenced Tagged Image File Format)
    RASTER_FORMAT_ATTR = _rasterFormatName
    -> S3Uploader_3
S3Uploader_3
    S3_ACCELERATION = No
    S3_BUCKET_NAME = your bucket
    S3_CANNED_ACL = Private
    S3_DATA = @Value(_rasterBlob)
    S3_URI_ATTRIBUTE = _s3_object_uri
    S3_UPLOAD_ENCRYPTION = None
    S3_OBJECT_KEY = Planet/basemap/basemap.tif
    S3_AWS_REGION = US West, Oregon (us-west-2)
    S3_FILE_OR_DATA = Attribute or Expression
    -> FeatureReader_4 [INITIATOR]

Bookmark: Add vector layer and generate tile cache
Note: If the basemap was updated, initiate reading / of the San Francisco transit dataset
FeatureReader_4
    GTFS_QUERY_FEATURE_TYPES_FOR_MERGE_FILTERS = Yes
    OUTPUT_FEATURES_DISPLAY = Schema and Data Features
    FEATURETYPES = shapes trips routes
    ATTR_ACCUM_MODE = Only Use Result
    COMBINE_GEOM = Use Result
    DATASET = https://gtfs.sfmta.com/transitdata/google_transit.zip
    INTERACT = <No Spatial Filter>
    FORMAT = GTFS
    ATTRIBUTES = agency,"fme_geometry{0},agency_id,agency_name,agency_url,agency_timezone,agency_lang,agency_phone,agency_fare_url",calendar,"fme_geometry{0},service_id,monday,tuesday,wednesday,thursday,friday,saturday,sunday,start_date,end_date",calendar_dates,"fme_geometry{0},service_id,date,exception_type",fare_attributes,"fme_geometry{0},fare_id,price,currency_type,payment_method,transfers,transfer_duration",fare_rules,"fme_geometry{0},fare_id,route_id,origin_id,destination_id,contains_id",feed_info,"fme_geometry{0},feed_publisher_name,feed_publisher_url,feed_lang,feed_start_date,feed_end_date,feed_version",frequencies,"fme_geometry{0},trip_id,start_time,end_time,headway_secs,exact_times",routes,"fme_geometry{0},route_id,agency_id,route_short_name,route_long_name,route_desc,route_type,route_url,route_color,route_text_color",shapes,"fme_geometry{0},shape_id",stop_times,"fme_geometry{0},trip_id,arrival_time,departure_time,stop_id,stop_sequence,stop_headsign,pickup_type,drop_off_type,shape_dist_traveled,timepoint",stops,"fme_geometry{0},stop_id,stop_code,stop_name,stop_desc,zone_id,stop_url,location_type,parent_station,stop_timezone,wheelchair_boarding",transfers,"fme_geometry{0},from_stop_id,to_stop_id,transfer_type,min_transfer_time",trips,"fme_geometry{0},route_id,service_id,trip_id,trip_headsign,trip_short_name,direction_id,block_id,shape_id,wheelchair_accessible,bikes_allowed"
    shapes -> GeometryExtractor
    trips -> InlineQuerier [trips]
    routes -> InlineQuerier [routes]
Note: Extract geometry to pass into through InlineQuerier
GeometryExtractor
    ATTR = _geometry
    KIND_LONG = FME XML
    REMOVE_GEOMETRY = No
    OGEOSMS_URL_PREFIX = http://maps.google.com/?q=
    OGC_WKT_PRECISION_DISPLAY = Shortened 64-bit
    OGCVERSION = 1.2
    PREFER_POLYGON_OVER_SURFACE = No
    -> InlineQuerier [shapes]
Note: Get all the routes with their names/numbers
InlineQuerier
    TABLE_DEF = shapes,shape_id,text,_geometry,text,trips,route_id,text,service_id,text,trip_id,text,trip_headsign,text,trip_short_name,text,direction_id,integer,block_id,text,shape_id,text,wheelchair_accessible,integer,bikes_allowed,integer,routes,route_id,text,agency_id,text,route_short_name,text,route_long_name,text,route_desc,text,route_type,text,route_url,text,route_color,text,route_text_color,text
    QUERY_SCHEMA = Routes,route_id,text,route_short_name,text,route_type,text,_geometry,text
    QUERY_DEF:
      Routes,SELECT distinct r.route_id, r.route_short_name,r.route_type, s._geometry
      FROM routes r
      INNER JOIN trips t ON
      t.route_id = r.route_id
      INNER JOIN shapes s ON
      t.shape_id = s.shape_id,FIRST
    Routes -> GeometryReplacer
Note: Restore route geometry
GeometryReplacer
    REMOVE_ATTRIBUTE = Yes
    MSSQL_FORMAT_CHOICE = Geometry
    OUTPUT_POINT_DISPLAY = Point
    OGC_WKT_PRECISION_DISPLAY = 64-bit
    SOURCE = @Value(_geometry)
    SRS_AXIS_ORDER_DISPLAY = Automatic
    KIND_LONG = FME XML
    ELLIPSOID_NAME = WGS84
    LETTERING = WGS84
    -> MeasureRemover
MeasureRemover
    REMOVE_ALL = Yes
    -> Reprojector_2
Note: Bring to UTM
Reprojector_2
    SOURCE = LL84
    RASTER_CELL_SIZE = Preserve Cells
    DEST = UTM83-10
    INTERPOLATION_TYPE_NAME = Nearest Neighbor
    REPROJECTED -> TestFilter
Note: Enforce the order of the different transit types, / buses, the thinnest line, goes on top of the others
Sorter_2
    SORT_PARM = _sort NUMERIC ASCENDING
    SORTED -> MapnikRasterizer [Routes]
    SORTED -> Intersector
Note: Make a nice raster / from the transit vector data / and Planet background
MapnikRasterizer
    LAYER_CARDINALITY = Each rendering rule is a layer
    BACKGROUND_COLOR = 1,1,1
    INTERPRETATION_TYPE = RGBA32
    SPACING = 2.5
    REFERENCED_FILES = $(FME_MF_DIR)SFTransitwithPlanetBasemapPublic/C:\Users\dbagh\Documents\Data\Maki\mapbox-maki-38626f2\renders\circle-12.png
    MAPNIK_CONFIG = Background;raster;__ignore__raster-properties-group;;opacity;1;scaling;near;__ignore__comp-group;;comp-op;src-over;Routes;line;__ignore__color-group;;stroke;@Value(fme_color);stroke-opacity;1;__ignore__line-style-group;;stroke-width;@Value(_width);stroke-linejoin;miter;stroke-linecap;butt;stroke-dasharray;;stroke-miterlimit;4;__ignore__positioning-group;FME_DISCLOSURE_CLOSED;offset;0;__ignore__smoothing-group;FME_DISCLOSURE_CLOSED;stroke-gamma;1;stroke-gamma-method;power;smooth;0;rasterizer;full;__ignore__comp-group;FME_DISCLOSURE_CLOSED;comp-op;src-over;BusLabels;text;__ignore__text-properties-group;;name;_concatenated;face-name;Tahoma,Normal;size;12;__ignore__color-group;;fill;@Value(fme_color);opacity;1;halo-fill;1,1,1;halo-radius;2;__ignore__positioning-group;FME_DISCLOSURE_OPEN;text-ratio;0;wrap-width;0;wrap-before;No;spacing;500;character-spacing;0;line-spacing;0;label-position-tolerance;0;dx;0;dy;0;avoid-edges;No;minimum-distance;0;minimum-padding;0;minimum-path-length;0;allow-overlap;No;orientation;0;placement;line;placement-type;dummy;placements;<Unused>;max-char-angle-delta;22.5;horizontal-alignment;auto;justify-alignment;auto;vertical-alignment;auto;__ignore__comp-group;;comp-op;src-over;TramLabels;text;__ignore__text-properties-group;;name;_concatenated;face-name;Tahoma,Bold;size;13;__ignore__color-group;;fill;@Value(fme_color);opacity;1;halo-fill;1,1,1;halo-radius;2;__ignore__positioning-group;FME_DISCLOSURE_OPEN;text-ratio;0;wrap-width;0;wrap-before;No;spacing;500;character-spacing;0;line-spacing;0;label-position-tolerance;0;dx;0;dy;0;avoid-edges;No;minimum-distance;0;minimum-padding;0;minimum-path-length;0;allow-overlap;No;orientation;0;placement;line;placement-type;dummy;placements;<Unused>;max-char-angle-delta;22.5;horizontal-alignment;auto;justify-alignment;auto;vertical-alignment;auto;__ignore__comp-group;;comp-op;src-over;CableLabels;text;__ignore__text-properties-group;;name;_concatenated;face-name;Tahoma,Bold;size;14;__ignore__color-group;;fill;@Value(fme_color);opacity;1;halo-fill;1,1,1;halo-radius;2;__ignore__positioning-group;FME_DISCLOSURE_OPEN;text-ratio;0;wrap-width;0;wrap-before;No;spacing;500;character-spacing;0;line-spacing;0;label-position-tolerance;0;dx;0;dy;0;avoid-edges;No;minimum-distance;0;minimum-padding;0;minimum-path-length;0;allow-overlap;No;orientation;0;placement;line;placement-type;dummy;placements;<Unused>;max-char-angle-delta;22.5;horizontal-alignment;auto;justify-alignment;auto;vertical-alignment;auto;__ignore__comp-group;;comp-op;src-over;stops;point;__ignore__point-properties-group;;__ignore__symbol-type;Image;file;C:\Users\dbagh\Documents\Data\Maki\mapbox-maki-38626f2\renders\circle-12.png;opacity;1;__ignore__positioning-group;FME_DISCLOSURE_OPEN;placement;centroid;allow-overlap;No;ignore-placement;No;transform;;__ignore__comp-group;;comp-op;src-over
    BACKGROUND_COLOR_ALPHA = 1.0
    SPECIFY_GROUND_EXTENTS = Use input data ground extents
    COLROW_OR_SPACING = Spacing
    RASTER -> SFtransit (writer GEOTIFF_1) [off]
    RASTER -> WebMapTiler
Note: Save a local copy of the map
SFtransit (writer GEOTIFF_1)
Note: Tile the raster to web tiles
WebMapTiler
    TILE_ROW_ATTRIBUTE = _tile_row
    TILE_SCHEME = GoogleMapsCompatible
    INTERPOLATION_TYPE_NAME = Bicubic
    ZOOM_LEVEL_ATTRIBUTE = _zoom_level
    NUM_TILES_ATTRIBUTE = _num_tiles
    MIN_ZOOM_LEVEL = 10
    TILE_COLUMN_ATTRIBUTE = _tile_column
    QUADKEY_ATTRIBUTE = _quadkey
    RASTER_INDEX_ATTRIBUTE = _raster_index
    MAX_ZOOM_LEVEL = 16
    TILES -> StringConcatenator [off]
    TILES -> RasterExtractor
Note: Make the tile name / (including a portion of the path for fanout)
StringConcatenator
    PARM_LINE = @Value(_zoom_level)\@Value(_tile_column)
    ACTION = Create New Attribute
    VAL_ATTR = _result
    -> GEOTIFF (writer PNGRASTER_1)
Note: Save tiles locally. Use fanout on both feature type and dataset level)
GEOTIFF (writer PNGRASTER_1)

Bookmark: Create colours, widths, sorting order, snap and change case where necessary
TestFilter
    DEFAULT_VALUE = Cablecar
    TEST_LIST = BOOL_OP,OR,COMPOSITE_TEST,<Unused>,TEST_CLAUSE,"TEST @Value(route_type) = 0",Tram,BOOL_OP,OR,COMPOSITE_TEST,<Unused>,TEST_CLAUSE,"TEST @Value(route_type) = 3",Bus
    Tram -> FeatureColorSetter
    Bus -> FeatureColorSetter_2
    Cablecar -> FeatureColorSetter_3
FeatureColorSetter
    MODE = Fixed
    COLOR = 1,0,0
    COLORED -> Snapper
Snapper
    SNAPTYPE_PARAM = Segment Snapping
    TOLERANCE = 5
    CLEANING_TOLERANCE = 5
    CLEANING_TOLERANCE_MODE = CUSTOM
    SNAPPED -> AttributeCreator_4
AttributeCreator_4
    ATTR_TABLE:
      SET_TO _width = 2.5
      SET_TO _sort = 1
    -> Sorter_2
FeatureColorSetter_2
    MODE = Fixed
    COLOR = 0,0.333333,1
    COLORED -> AttributeCreator_5
AttributeCreator_5
    ATTR_TABLE:
      SET_TO _width = 1.5
      SET_TO _sort = 2
    -> Sorter_2
FeatureColorSetter_3
    MODE = Fixed
    COLOR = 0.333333,0,0
    COLORED -> StringCaseChanger
StringCaseChanger
    CHANGE_TYPE = Full Title Case
    ATTRCHOICE = Selected Attributes
    ATTRLIST = route_short_name
    -> AttributeCreator_6
AttributeCreator_6
    ATTR_TABLE:
      SET_TO _width = 3
      SET_TO _sort = 0
    -> Sorter_2

Bookmark: Clean the routes for better labelling results (remove duplicate geometries, but concatenate route names)
Intersector
    ATTRS_ACCUM_MODE = Use Attributes From One Feature
    GRP_BY = route_type
    PERFORM_SELF_INTERSECTION = Yes
    OV_ATTR = _overlaps
    LIST_ATTRS_TO_INCLUDE = route_short_name
    MEASURE_TYPE = Continuous
    GENERATE_LIST_DROP = YES
    SEPARATE_COLLINEAR_SEGMENTS = Yes
    LIST_NAME = list
    DUPLICATE_Z_NODES = No
    SEG_ATTR = _segments
    DEAGGREGATE_INPUT = Yes
    INTERSECTED -> Matcher_3
Matcher_3
    CNT_ATTR = _match_id
    BLANK_AND_MISSING_DIFFER = No
    MATCH_STRATEGY = Match Selected Attributes
    MATCH = FULL
    LENIENT_MATCH = Yes
    MATCHATTRS = route_short_name
    SINGLE_MATCHED -> ListDuplicateRemover
ListDuplicateRemover
    SRC_LIST = list{}.route_short_name
    -> ListSorter
ListSorter
    SRC_LIST = list{}.route_short_name
    TYPE = Alphabetic
    ORDER = Ascending
    -> ListConcatenator
ListConcatenator
    LIST_ATTR = list{}.route_short_name
    DROP_EMPTY_PARTS = Yes
    SEP = ,
    VAL_ATTR = _concatenated
    -> LineCombiner
LineCombiner
    CONNECT_Z_MODE = First Wins
    CONSIDER_NODE_ELEVATION = no
    GROUP_BY = _concatenated
    PRESERVE = no
    LINES_AS_SEGMENTS = No
    TOPOLOGY = End noded
    ACCUM_ATTRS_NAME = Use Attributes From One Feature
    BREAK = no
    LINE -> TestFilter_2
TestFilter_2
    DEFAULT_VALUE = Cablecar
    TEST_LIST = BOOL_OP,OR,COMPOSITE_TEST,<Unused>,TEST_CLAUSE,"TEST @Value(route_type) = 3",Bus,BOOL_OP,OR,COMPOSITE_TEST,<Unused>,TEST_CLAUSE,"TEST @Value(route_type) = 0",Tram
    Bus -> MapnikRasterizer [BusLabels]
    Tram -> MapnikRasterizer [TramLabels]
    Cablecar -> MapnikRasterizer [CableLabels]

Bookmark: Upload fresh tiles to S3
RasterExtractor
    RASTER_BLOB_ATTR = _rasterBlob
    RASTER_FORMAT = PNG (Portable Network Graphics)
    RASTER_FORMAT_ATTR = _rasterFormatName
    -> S3Uploader_2
S3Uploader_2
    S3_ACCELERATION = No
    S3_BUCKET_NAME = your bucket
    S3_CANNED_ACL = Public Read
    S3_DATA = @Value(_rasterBlob)
    S3_URI_ATTRIBUTE = _s3_object_uri
    S3_UPLOAD_ENCRYPTION = None
    S3_OBJECT_KEY = Planet/tiles/@Value(_zoom_level)/@Value(_tile_column)/@Value(_tile_row).png
    S3_AWS_REGION = US West, Oregon (us-west-2)
    S3_FILE_OR_DATA = Attribute or Expression
    -> S3Uploader_2_Output
S3Uploader_2_Output: Logger
    MAXFEATS = 20
    MESSAGE = Feature is:
    MAXCOORDS = 20
